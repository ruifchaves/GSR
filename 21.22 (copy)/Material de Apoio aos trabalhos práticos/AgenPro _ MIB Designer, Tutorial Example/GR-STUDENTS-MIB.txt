-- Tutorial Example
-- MIB Design and SNMP Agent Code Generation
-- Universidade do Minho, v1.0 February 2021
-- (c) João Pereira, d12267@di.uminho.pt
-- Disclaimer: This software/specification can be freely used and altered 
-- but the author should be acknowledged. Also, the author bears no 
-- responsibility on the use of this software/specification by a third person.



GR-STUDENTS-MIB DEFINITIONS ::= BEGIN

IMPORTS
	enterprises,
	MODULE-IDENTITY,
	OBJECT-TYPE,
	Counter32
		FROM SNMPv2-SMI
	OBJECT-GROUP
		FROM SNMPv2-CONF;

grMIB MODULE-IDENTITY
	LAST-UPDATED "202102041458Z"	-- Feb 4, 2021, 2:58:00 PM
	ORGANIZATION ""
	CONTACT-INFO
		""
	DESCRIPTION
		"MIB to aggregate students info"
	REVISION "202102041458Z"	-- Feb 4, 2021, 2:58:00 PM
	DESCRIPTION
		"Initial version."
	-- 1.3.6.1.4.1.8888
	::= { enterprises 8888 }


grMIBTotalStudents OBJECT-TYPE
	SYNTAX  Counter32
	MAX-ACCESS read-only
	STATUS  current
	DESCRIPTION
		""
	-- 1.3.6.1.4.1.8888.1
	::= { grMIB 1 }


grMIBTotalStudentsMIETI OBJECT-TYPE
	SYNTAX  Counter32
	MAX-ACCESS read-only
	STATUS  current
	DESCRIPTION
		""
	-- 1.3.6.1.4.1.8888.2
	::= { grMIB 2 }


grMIBTotalStudentsMIEI OBJECT-TYPE
	SYNTAX  Counter32
	MAX-ACCESS read-only
	STATUS  current
	DESCRIPTION
		""
	-- 1.3.6.1.4.1.8888.3
	::= { grMIB 3 }


grMIBTotalStudentsMEI OBJECT-TYPE
	SYNTAX  Counter32
	MAX-ACCESS read-only
	STATUS  current
	DESCRIPTION
		""
	-- 1.3.6.1.4.1.8888.4
	::= { grMIB 4 }


grMIBTotalStudentsMERSTEL OBJECT-TYPE
	SYNTAX  Counter32
	MAX-ACCESS read-only
	STATUS  current
	DESCRIPTION
		""
	-- 1.3.6.1.4.1.8888.5
	::= { grMIB 5 }


grMIBTable OBJECT-TYPE
	SYNTAX  SEQUENCE OF GrMIBEntry
	MAX-ACCESS not-accessible
	STATUS  current
	DESCRIPTION
		""
	-- 1.3.6.1.4.1.8888.6
	::= { grMIB 6 }


grMIBEntry OBJECT-TYPE
	SYNTAX  GrMIBEntry
	MAX-ACCESS not-accessible
	STATUS  current
	DESCRIPTION
		""
	INDEX {
		index }
	-- 1.3.6.1.4.1.8888.6.1
	::= { grMIBTable 1 }


GrMIBEntry ::= SEQUENCE {

	index    Counter32,
	number   INTEGER,
	course   OCTET STRING,
	name     OCTET STRING,
	email    OCTET STRING,
	tpStatus INTEGER }


index OBJECT-TYPE
	SYNTAX  Counter32
	MAX-ACCESS read-only
	STATUS  current
	DESCRIPTION
		""
	-- 1.3.6.1.4.1.8888.6.1.1
	::= { grMIBEntry 1 }


number OBJECT-TYPE
	SYNTAX  INTEGER
	MAX-ACCESS read-only
	STATUS  current
	DESCRIPTION
		""
	-- 1.3.6.1.4.1.8888.6.1.2
	::= { grMIBEntry 2 }


course OBJECT-TYPE
	SYNTAX  OCTET STRING
	MAX-ACCESS read-only
	STATUS  current
	DESCRIPTION
		""
	-- 1.3.6.1.4.1.8888.6.1.3
	::= { grMIBEntry 3 }


name OBJECT-TYPE
	SYNTAX  OCTET STRING
	MAX-ACCESS read-only
	STATUS  current
	DESCRIPTION
		""
	-- 1.3.6.1.4.1.8888.6.1.4
	::= { grMIBEntry 4 }


email OBJECT-TYPE
	SYNTAX  OCTET STRING
	MAX-ACCESS read-only
	STATUS  current
	DESCRIPTION
		""
	-- 1.3.6.1.4.1.8888.6.1.5
	::= { grMIBEntry 5 }


tpStatus OBJECT-TYPE
	SYNTAX  INTEGER
	UNITS
		"0 - no delivery
		1 - TP1 delivered
		2 - TP2 delivered
		4 - TP3 delivered
		3 - TP1 + TP2
		5 - TP1 + TP3
		6 - TP2 + TP3
		7 - TP1 +TP2 +TP3"
	MAX-ACCESS read-write
	STATUS  current
	DESCRIPTION
		""
	-- 1.3.6.1.4.1.8888.6.1.6
	::= { grMIBEntry 6 }


-- Conformance
--

grMIBConf OBJECT IDENTIFIER 
	-- 1.3.6.1.4.1.8888.7
	::= { grMIB 7 }

-- Groups
--

grMIBGroups OBJECT IDENTIFIER 
	-- 1.3.6.1.4.1.8888.7.2
	::= { grMIBConf 2 }

-- Compliances
--

grMIBCompliances OBJECT IDENTIFIER 
	-- 1.3.6.1.4.1.8888.7.3
	::= { grMIBConf 3 }

grMIBBasicGroup OBJECT-GROUP
	OBJECTS {
		grMIBTotalStudents,
		grMIBTotalStudentsMIETI,
		grMIBTotalStudentsMIEI,
		grMIBTotalStudentsMEI,
		grMIBTotalStudentsMERSTEL,
		index,
		number,
		course,
		name,
		email,
		tpStatus }
	STATUS  current
	DESCRIPTION
		"Basic objects."
	-- 1.3.6.1.4.1.8888.7.2.1
	::= { grMIBGroups 1 }

END
